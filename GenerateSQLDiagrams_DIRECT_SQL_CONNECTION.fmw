FME workspace GenerateSQLDiagrams_DIRECT_SQL_CONNECTION.fmw
Title: GenerateSQLDiagrams_DIRECT_SQL_CONNECTION

Bookmark: Table View Relationships based on View Definitions
Note: Using Table -> View Relationships as defined by the View Definition and what tables are referenced
SQLCreator_2
    EXPOSED_ATTRIBUTE_LIST = view_name view_type referenced_entity_name entity_type
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = HomeStorage AdventureWorks2019
    MSSQL_ADO_QUERY_FEATURE_TYPES_FOR_MERGE_FILTERS = Yes
    SQL_STATEMENT:
      select distinct schema_name(v.schema_id) as schema_name,
             v.name as view_name,
      	   v.type_desc as view_type,
             schema_name(o.schema_id) as referenced_schema_name,
             o.name as referenced_entity_name,
             o.type_desc as entity_type
      from sys.views v
      join sys.sql_expression_dependencies d
           on d.referencing_id = v.object_id
           and d.referenced_id is not null
      join sys.objects o
           on o.object_id = d.referenced_id
       order by schema_name,
                view_name;
    RESULT -> TestFilter
Note: STRONGLY SUGGEST SPLITTING INTO SMALLER STREAMS FOR INITIAL INVESTIGATION
TestFilter
    DEFAULT_VALUE = Other
    TEST_LIST:
      "BOOL_OP,OR,COMPOSITE_TEST,""""""1 OR 2"""""",TEST_CLAUSE,CASE_INSENSITIVE_TEST @Value(view_name) CONTAINS Sale
      CASE_INSENSITIVE_TEST @Value(referenced_entity_name) CONTAINS Sale",Sales,"BOOL_OP,OR,COMPOSITE_TEST,""""""1 OR 2"""""",TEST_CLAUSE,CASE_INSENSITIVE_TEST @Value(view_name) CONTAINS Employ
      CASE_INSENSITIVE_TEST @Value(referenced_entity_name) CONTAINS Employ",Employee
    Sales -> Create_JSON_Stream
    Employee -> Create_JSON_Stream_2
Create_JSON_Stream
    pDestination = referenced_entity_name
    pDestinationType = entity_type
    pHeading = Sales
    pSource = view_name
    pSourceType = view_type
    -> GenerateNetworkGraphs [BuildNetworkGraphs_Input]
Create_JSON_Stream_2
    pDestination = referenced_entity_name
    pDestinationType = entity_type
    pHeading = Employees
    pSource = view_name
    pSourceType = view_type
    -> GenerateNetworkGraphs [BuildNetworkGraphs_Input]

Bookmark: Generate Graphs
GenerateNetworkGraphs
    pDefaultNodeColor = purple
    pJson = json
    pLabelFontSize = 12
    pNodeSizeMultiplier = 1.2
    pPageHeading = Heading
    pPhysicsAvoidOverlap = 0.5
    pPhysicsEnabled = false
    pPhysicsMinVelocity = 3
    pTableNodeColor = red
    pViewNodeColor = blue
GenerateNetworkGraphs_2
    pDefaultNodeColor = purple
    pJson = json
    pLabelFontSize = 12
    pNodeSizeMultiplier = 1.2
    pPageHeading = Heading
    pPhysicsAvoidOverlap = 0.5
    pPhysicsEnabled = false
    pPhysicsMinVelocity = 3
    pTableNodeColor = red
    pViewNodeColor = blue

Bookmark: Foreign Key Relations
Note: Using Primary/Foreign Key Relationships
SQLCreator
    EXPOSED_ATTRIBUTE_LIST = "Parent table" "Refrenced table"
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = HomeStorage AdventureWorks2019
    MSSQL_ADO_QUERY_FEATURE_TYPES_FOR_MERGE_FILTERS = Yes
    SQL_STATEMENT:
      SELECT distinct
          --fk.name 'FK Name',
          tp.name 'Parent table',
         -- cp.name, cp.column_id,
          tr.name 'Refrenced table'
          --cr.name, cr.column_id
      FROM
          sys.foreign_keys fk
      INNER JOIN
          sys.tables tp ON fk.parent_object_id = tp.object_id
      INNER JOIN
          sys.tables tr ON fk.referenced_object_id = tr.object_id
      INNER JOIN
          sys.foreign_key_columns fkc ON fkc.constraint_object_id = fk.object_id
      INNER JOIN
          sys.columns cp ON fkc.parent_column_id = cp.column_id AND fkc.parent_object_id = cp.object_id
      INNER JOIN
          sys.columns cr ON fkc.referenced_column_id = cr.column_id AND fkc.referenced_object_id = cr.object_id
    RESULT -> Create_JSON_Stream_3
Create_JSON_Stream_3
    pDestination = Refrenced table
    pHeading = FK Relations
    pSource = Parent table
    -> GenerateNetworkGraphs_2 [BuildNetworkGraphs_Input]

FME custom transformer Create_JSON_Stream

Parameters:
- pDestination =
- pDestinationType =
- pHeading =
- pSource =
- pSourceType =

Input (input)
    -> AttributeCreator
AttributeCreator
    ATTR_TABLE:
      SET_TO source = @Value($(pSource))
      SET_TO sourceType = @Value($(pSourceType))
      SET_TO destination = @Value($(pDestination))
      SET_TO destinationType = @Value($(pDestinationType))
    -> JSONTemplater_9 [ROOT]
JSONTemplater_9
    RESULT_ATTRIBUTE = _result
    ROOT_QUERY_EXPR:
      {
          "source": fme:get-attribute("source"),
          "sourceType": fme:get-attribute("sourceType"),
          "destination": fme:get-attribute("destination"),
          "destinationType": fme:get-attribute("destinationType")
      }
    VISIBLE_QUERY_VALIDATE = Yes
    -> JSONTemplater_8 [SUB]
Creator
    GEOMTYPE = Geometry Object
    NUM = 1
    CREATED -> JSONTemplater_8 [ROOT]
JSONTemplater_8
    RESULT_ATTRIBUTE = json
    ROOT_QUERY_EXPR:
      [
      fme:process-features("SUB")
      ]
    SUB_QUERY_EXPR = fme:get-json-attribute("_result")
    VISIBLE_QUERY_VALIDATE = Yes
    -> AttributeCreator_2
AttributeCreator_2
    ATTR_TABLE = SET_TO Heading = $(pHeading)
    -> Output (output)
Output (output)

FME custom transformer GenerateNetworkGraphs

Parameters:
- pDefaultNodeColor =
- pJson =
- pLabelFontSize =
- pNodeColorMessage =
- pNodeOptions =
- pNodeSizeMultiplier =
- pPageHeading =
- pPhysics =
- pPhysicsAvoidOverlap =
- pPhysicsEnabled =
- pPhysicsMinVelocity =
- pTableNodeColor =
- pViewNodeColor =

BuildNetworkGraphs_Input (input)
    -> AttributeCreator
AttributeCreator
    ATTR_TABLE:
      SET_TO Heading = @Value($(pPageHeading))
      SET_TO JSON = @Value($(pJson))
      SET_TO LabelFontSize = $(pLabelFontSize)
      SET_TO NodeSizeMultiplier = $(pNodeSizeMultiplier)
      SET_TO PhysicsEnabled = $(pPhysicsEnabled)
      SET_TO PhysicsMinimumVelocity = $(pPhysicsMinVelocity)
      SET_TO PhysicsAvoidOverlap = $(pPhysicsAvoidOverlap)
      SET_TO ViewNodeColor = $(pViewNodeColor)
      SET_TO TableNodeColor = $(pTableNodeColor)
      SET_TO DefaultNodecolor = $(pDefaultNodeColor)
    -> BuildNetworkGraphs
BuildNetworkGraphs: PythonCaller
    PYTHONSOURCE:
      import fme
      import fmeobjects
      import os
      import pandas as pd
      import networkx as nx
      import matplotlib
      matplotlib.use('agg')
      import matplotlib.pyplot as plt
      from pyvis.network import Network
      outputFiles = []




      class FeatureProcessor(object):
          """Template Class Interface:
          When using this class, make sure its name is set as the value of the 'Class
          to Process Features' transformer parameter.
          """



          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """

              heading = feature.getAttribute('Heading')
              outputPath = FME_MacroValues['FME_MF_DIR']
              outputFileName = f'{heading}.html'
              outputFile = os.path.join(outputPath, outputFileName)
              json = feature.getAttribute('JSON')
              labelFontSize = str(feature.getAttribute('LabelFontSize'))
              nodeSizeMultiplier = float(feature.getAttribute('NodeSizeMultiplier'))
              enablePhysics = feature.getAttribute('PhysicsEnabled')
              physicsMinVelocity = str(feature.getAttribute('PhysicsMinimumVelocity'))
              physicsAvoidOverlap = str(feature.getAttribute('PhysicsAvoidOverlap'))
              viewNodeColor = feature.getAttribute('ViewNodeColor')
              tableNodecolor = feature.getAttribute('TableNodeColor')
              defaultNodeColor = feature.getAttribute('DefaultNodecolor')

              #Create new Network with 100% height and width
              net = Network(height='94%', width='100%', heading=heading)

              #load JSON into pandas dataframe
              df = pd.read_json(json, orient='records')

              #Create new networkx graph from pandas edgelist
              G = nx.from_pandas_edgelist(df, source="source", target="destination")

              #Create pyvis network from networkx graph
              net.from_nx(G)


              #Adjust Node Size & Color
              nodeSize = {}
              nodeType = {}

              #Build size and Color Dicts
              for index, row in df.iterrows():
                  source = row['source']
                  destination = row['destination']
                  sourceType = row['sourceType']
                  destinationType = row['destinationType']


                  #Size Dict
                  if source not in nodeSize.keys():
                      nodeSize[source] = 10
                  else:
                      nodeSize[source] *= nodeSizeMultiplier
                  if destination not in nodeSize.keys():
                      nodeSize[destination] = 10
                  else:
                      nodeSize[destination] *= nodeSizeMultiplier

                  #Color Dict
                  if destination not in nodeType.keys():
                      nodeType[destination] = destinationType
                  if source not in nodeType.keys():
                      nodeType[source] = sourceType

              #Set node Size
              for n in net.nodes:
                  n['size'] = nodeSize[n['id']]

              #Set node Color
              for n in net.nodes:
                  if nodeType[n['id']] == "VIEW":
                      n['color'] = viewNodeColor

                  elif nodeType[n['id']] == "USER_TABLE":
                      n['color'] = tableNodecolor

                  else:
                      pass
                      n['color'] = defaultNodeColor




              #Set node title
              neighbor_map = net.get_adj_list()

              for n in net.nodes:
                  n['title'] = ' Neighbors:' + '  |  '.join(neighbor_map[n['id']])

              #Set edge color
              for e in net.edges:
                  e['color'] = 'black'

              #Set pyvis network options
              net.set_options("""
                  const options = {
                    "nodes": {
                      "color": {
                        "highlight" : {
                          "border" : "rgba(129,11,233,1)"
                        }
                      },
                      "font": {
                        "size":""" + labelFontSize + """,
                        "face": "verdana",
                        "strokeWidth": 2
                      },
                      "shadow": {
                        "enabled": true,
                        "size": 9,
                        "x": 6,
                        "y": 7
                      },
                      "shapeProperties": {
                        "borderRadius": 3
                      },
                      "size": null
                    },
                    "physics": {
                      "enabled" :""" + enablePhysics + """,
                      "barnesHut": {
                        "avoidOverlap": """ + physicsAvoidOverlap + """
                      },
                      "minVelocity": """ + physicsMinVelocity + """
                    }
                  }
                  """)

              #Show network
              net.show(outputFile)

              outputFiles.append(outputFile)



          def close(self):
              """This method is called once all the FME Features have been processed
              from input().
              """
              print(outputFiles)
              for f in outputFiles:
                  newFeature = fmeobjects.FMEFeature()
                  newFeature.setAttribute('file_path', f)
                  self.pyoutput(newFeature)


          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> AttributeExposer
AttributeExposer
    ATTR_LIST = file_path
    -> AttributeKeeper
AttributeKeeper
    CREATE_BULK_MODE_FEATURES = NO
    KEEP_ATTRS = file_path
    -> HTMLFiles (output)
HTMLFiles (output)
