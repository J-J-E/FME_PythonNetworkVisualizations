FME workspace GenerateSQLDiagrams_JSON_FILE_LOCAL.fmwt
Title: GenerateSQLDiagrams_JSON_FILE_LOCAL

Creator
    GEOMTYPE = Geometry Object
    NUM = 1
    CREATED -> FeatureReader [INITIATOR]
    CREATED -> FeatureReader_2 [INITIATOR]
FeatureReader
    ATTRIBUTES = text_line,"text_line_data,fme_geometry{0}"
    ATTRS_TO_EXPOSE = fme_feature_type
    ATTR_ACCUM_MODE = Only Use Result
    COMBINE_GEOM = Use Result
    DATASET = $(FME_MF_DIR)ExampleData/Employees.json
    FORMAT = TEXTLINE
    OUTPUT_FEATURES_DISPLAY = Schema and Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    text_line -> AttributeCreator
AttributeCreator
    ATTR_TABLE = SET_TO Heading = Employees
    -> GenerateNetworkGraphs_2 [BuildNetworkGraphs_Input]
FeatureReader_2
    ATTRIBUTES = text_line,"text_line_data,fme_geometry{0}"
    ATTR_ACCUM_MODE = Only Use Result
    COMBINE_GEOM = Use Result
    DATASET = $(FME_MF_DIR)ExampleData/Sales.json
    FORMAT = TEXTLINE
    OUTPUT_FEATURES_DISPLAY = Schema and Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    text_line -> AttributeCreator_2
AttributeCreator_2
    ATTR_TABLE = SET_TO Heading = Sales
    -> GenerateNetworkGraphs_2 [BuildNetworkGraphs_Input]
GenerateNetworkGraphs_2
    pDefaultNodeColor = purple
    pJson = text_line_data
    pLabelFontSize = 12
    pNodeSizeMultiplier = 1.2
    pPageHeading = Heading
    pPhysicsAvoidOverlap = 0.5
    pPhysicsEnabled = true
    pPhysicsMinVelocity = 3
    pTableNodeColor = red
    pViewNodeColor = blue

FME custom transformer GenerateNetworkGraphs

Parameters:
- pDefaultNodeColor =
- pJson =
- pLabelFontSize =
- pNodeColorMessage =
- pNodeOptions =
- pNodeSizeMultiplier =
- pPageHeading =
- pPhysics =
- pPhysicsAvoidOverlap =
- pPhysicsEnabled =
- pPhysicsMinVelocity =
- pTableNodeColor =
- pViewNodeColor =

BuildNetworkGraphs_Input (input)
    -> AttributeCreator
AttributeCreator
    ATTR_TABLE:
      SET_TO Heading = @Value($(pPageHeading))
      SET_TO JSON = @Value($(pJson))
      SET_TO LabelFontSize = $(pLabelFontSize)
      SET_TO NodeSizeMultiplier = $(pNodeSizeMultiplier)
      SET_TO PhysicsEnabled = $(pPhysicsEnabled)
      SET_TO PhysicsMinimumVelocity = $(pPhysicsMinVelocity)
      SET_TO PhysicsAvoidOverlap = $(pPhysicsAvoidOverlap)
      SET_TO ViewNodeColor = $(pViewNodeColor)
      SET_TO TableNodeColor = $(pTableNodeColor)
      SET_TO DefaultNodecolor = $(pDefaultNodeColor)
    -> BuildNetworkGraphs
BuildNetworkGraphs: PythonCaller
    PYTHONSOURCE:
      import fme
      import fmeobjects
      import os
      import pandas as pd
      import networkx as nx
      import matplotlib
      matplotlib.use('agg')
      import matplotlib.pyplot as plt
      from pyvis.network import Network
      outputFiles = []




      class FeatureProcessor(object):
          """Template Class Interface:
          When using this class, make sure its name is set as the value of the 'Class
          to Process Features' transformer parameter.
          """



          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """

              heading = feature.getAttribute('Heading')
              outputPath = FME_MacroValues['FME_MF_DIR']
              outputFileName = f'{heading}.html'
              outputFile = os.path.join(outputPath, outputFileName)
              json = feature.getAttribute('JSON')
              labelFontSize = str(feature.getAttribute('LabelFontSize'))
              nodeSizeMultiplier = float(feature.getAttribute('NodeSizeMultiplier'))
              enablePhysics = feature.getAttribute('PhysicsEnabled')
              physicsMinVelocity = str(feature.getAttribute('PhysicsMinimumVelocity'))
              physicsAvoidOverlap = str(feature.getAttribute('PhysicsAvoidOverlap'))
              viewNodeColor = feature.getAttribute('ViewNodeColor')
              tableNodecolor = feature.getAttribute('TableNodeColor')
              defaultNodeColor = feature.getAttribute('DefaultNodecolor')

              #Create new Network with 100% height and width
              net = Network(height='94%', width='100%', heading=heading)

              #load JSON into pandas dataframe
              df = pd.read_json(json, orient='records')

              #Create new networkx graph from pandas edgelist
              G = nx.from_pandas_edgelist(df, source="source", target="destination")

              #Create pyvis network from networkx graph
              net.from_nx(G)


              #Adjust Node Size & Color
              nodeSize = {}
              nodeType = {}

              #Build size and Color Dicts
              for index, row in df.iterrows():
                  source = row['source']
                  destination = row['destination']
                  sourceType = row['sourceType']
                  destinationType = row['destinationType']


                  #Size Dict
                  if source not in nodeSize.keys():
                      nodeSize[source] = 10
                  else:
                      nodeSize[source] *= nodeSizeMultiplier
                  if destination not in nodeSize.keys():
                      nodeSize[destination] = 10
                  else:
                      nodeSize[destination] *= nodeSizeMultiplier

                  #Color Dict
                  if destination not in nodeType.keys():
                      nodeType[destination] = destinationType
                  if source not in nodeType.keys():
                      nodeType[source] = sourceType

              #Set node Size
              for n in net.nodes:
                  n['size'] = nodeSize[n['id']]

              #Set node Color
              for n in net.nodes:
                  if nodeType[n['id']] == "VIEW":
                      n['color'] = viewNodeColor

                  elif nodeType[n['id']] == "USER_TABLE":
                      n['color'] = tableNodecolor

                  else:
                      pass
                      n['color'] = defaultNodeColor




              #Set node title
              neighbor_map = net.get_adj_list()

              for n in net.nodes:
                  n['title'] = ' Neighbors:' + '  |  '.join(neighbor_map[n['id']])

              #Set edge color
              for e in net.edges:
                  e['color'] = 'black'

              #Set pyvis network options
              net.set_options("""
                  const options = {
                    "nodes": {
                      "color": {
                        "highlight" : {
                          "border" : "rgba(129,11,233,1)"
                        }
                      },
                      "font": {
                        "size":""" + labelFontSize + """,
                        "face": "verdana",
                        "strokeWidth": 2
                      },
                      "shadow": {
                        "enabled": true,
                        "size": 9,
                        "x": 6,
                        "y": 7
                      },
                      "shapeProperties": {
                        "borderRadius": 3
                      },
                      "size": null
                    },
                    "physics": {
                      "enabled" :""" + enablePhysics + """,
                      "barnesHut": {
                        "avoidOverlap": """ + physicsAvoidOverlap + """
                      },
                      "minVelocity": """ + physicsMinVelocity + """
                    }
                  }
                  """)

              #Show network
              net.show(outputFile)

              outputFiles.append(outputFile)



          def close(self):
              """This method is called once all the FME Features have been processed
              from input().
              """
              print(outputFiles)
              for f in outputFiles:
                  newFeature = fmeobjects.FMEFeature()
                  newFeature.setAttribute('file_path', f)
                  self.pyoutput(newFeature)


          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> AttributeExposer
AttributeExposer
    ATTR_LIST = file_path
    -> AttributeKeeper
AttributeKeeper
    CREATE_BULK_MODE_FEATURES = NO
    KEEP_ATTRS = file_path
    -> HTMLFiles (output)
HTMLFiles (output)
