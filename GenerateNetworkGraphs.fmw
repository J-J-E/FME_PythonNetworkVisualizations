FME workspace GenerateNetworkGraphs.fmw
Title: GenerateSQLDiagrams_JSON_FILE_LOCAL

Note: Python Modules needed - pandas, networkx, matplotlib, pyvis / Installing Liibraries: / Windows command line example: / fme.exe python -m pip install pandas --target C:\Users\<user>\Documents\FME\Plugins\Python / Linux command line example: / ./fme python -m pip install pandas --target ~/Library/Application\ Support/FME/Plugins/Python
Creator_2
    GEOMTYPE = Geometry Object
    NUM = 1
    CREATED -> FeatureReader_3 [INITIATOR]
Note: Read Features from GitHub repo
FeatureReader_3
    ATTRS_TO_EXPOSE = referenced_entity_name referenced_entity_type referencer_name referencer_type
    ATTR_ACCUM_MODE = Only Use Result
    COMBINE_GEOM = Use Result
    DATASET = https://github.com/J-J-E/FME_PythonNetworkVisualizations/raw/main/ExampleDatabase.sqlite
    FEATURETYPES = RelationshipTable
    FORMAT = SQLITE3
    OUTPUT_FEATURES_DISPLAY = Schema and Data Features
    SQLITE3_QUERY_FEATURE_TYPES_FOR_MERGE_FILTERS = Yes
    SQLITE3_SUPPORT_INTERNATIONALIZATION = YES
    <OTHER> -> TestFilter
Note: Create Table Groupings
TestFilter
    DEFAULT_VALUE = <UNFILTERED>
    TEST_LIST:
      "BOOL_OP,OR,COMPOSITE_TEST,""""""1 OR 2"""""",TEST_CLAUSE,CASE_INSENSITIVE_TEST @Value(referencer_name) CONTAINS Employee
      CASE_INSENSITIVE_TEST @Value(referencer_name) CONTAINS Employee",Employee,"BOOL_OP,OR,COMPOSITE_TEST,""""""1 OR 2"""""",TEST_CLAUSE,CASE_INSENSITIVE_TEST @Value(referencer_name) CONTAINS Sales
      CASE_INSENSITIVE_TEST @Value(referencer_name) CONTAINS Sales",Sales
    Employee -> AttributeValueMapper
    Sales -> AttributeValueMapper_3
GenerateNetworkGraphs_2
    pDefaultNodeColor = grey
    pJson = json
    pLabelFontSize = 12
    pNodeSizeMultiplier = 1.12
    pPageHeading = Heading
    pPhysicsAvoidOverlap = 0.5
    pPhysicsEnabled = true
    pPhysicsMinVelocity = 3
    pPhysicsSolver = barnesHut

Bookmark: Conditionally Creeate Colors
AttributeValueMapper
    DIRECTION = Forward (Source To Destination)
    LUT = VIEW,BLUE
    SRC = referencer_type
    VAL_ATTR = referencer_color
    -> AttributeValueMapper_2
AttributeValueMapper_2
    DIRECTION = Forward (Source To Destination)
    LUT = USER_TABLE,RED
    SRC = referenced_entity_type
    VAL_ATTR = referenced_entity_color
    -> Create_JSON_Stream_2

Bookmark: Employee Tables Graph
Create_JSON_Stream_2
    pDestination = referenced_entity_name
    pDestinationColor = referenced_entity_color
    pHeading = Employee
    pSource = referencer_name
    pSourceColor = referencer_color
    -> GenerateNetworkGraphs_2 [BuildNetworkGraphs_Input]

Bookmark: Conditionally Creeate Colors
AttributeValueMapper_3
    DIRECTION = Forward (Source To Destination)
    LUT = VIEW,Purple
    SRC = referencer_type
    VAL_ATTR = referencer_color
    -> AttributeValueMapper_4
AttributeValueMapper_4
    DIRECTION = Forward (Source To Destination)
    LUT = USER_TABLE,Green
    SRC = referenced_entity_type
    VAL_ATTR = referenced_entity_color
    -> Create_JSON_Stream_3

Bookmark: Sales Tables Graph
Create_JSON_Stream_3
    pDestination = referenced_entity_name
    pDestinationColor = referenced_entity_color
    pHeading = Sales
    pSource = referencer_name
    pSourceColor = referencer_color
    -> GenerateNetworkGraphs_2 [BuildNetworkGraphs_Input]

FME custom transformer GenerateNetworkGraphs

Parameters:
- pDefaultNodeColor =
- pJson =
- pLabelFontSize =
- pNodeColorMessage =
- pNodeOptions =
- pNodeSizeMultiplier =
- pPageHeading =
- pPhysics =
- pPhysicsAvoidOverlap =
- pPhysicsEnabled =
- pPhysicsMinVelocity =
- pPhysicsSolver =

BuildNetworkGraphs_Input (input)
    -> AttributeCreator
AttributeCreator
    ATTR_TABLE:
      SET_TO Heading = @Value($(pPageHeading))
      SET_TO JSON = @Value($(pJson))
      SET_TO LabelFontSize = $(pLabelFontSize)
      SET_TO NodeSizeMultiplier = $(pNodeSizeMultiplier)
      SET_TO PhysicsSolver = $(pPhysicsSolver)
      SET_TO PhysicsEnabled = $(pPhysicsEnabled)
      SET_TO PhysicsMinimumVelocity = $(pPhysicsMinVelocity)
      SET_TO PhysicsAvoidOverlap = $(pPhysicsAvoidOverlap)
      SET_TO ViewNodeColor = blue
      SET_TO TableNodeColor = red
      SET_TO DefaultNodecolor = $(pDefaultNodeColor)
    -> BuildNetworkGraphs
BuildNetworkGraphs: PythonCaller
    PYTHONSOURCE:
      import fme
      import fmeobjects
      import os
      import pandas as pd
      import networkx as nx
      import matplotlib
      matplotlib.use('agg')
      import matplotlib.pyplot as plt
      from pyvis.network import Network
      outputFiles = []




      class FeatureProcessor(object):
          """Template Class Interface:
          When using this class, make sure its name is set as the value of the 'Class
          to Process Features' transformer parameter.
          """



          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """

              heading = feature.getAttribute('Heading')
              outputPath = FME_MacroValues['FME_MF_DIR']
              outputFileName = f'{heading}.html'
              outputFile = os.path.join(outputPath, outputFileName)
              labelFontSize = str(feature.getAttribute('LabelFontSize'))
              nodeSizeMultiplier = float(feature.getAttribute('NodeSizeMultiplier'))
              defaultNodeColor = feature.getAttribute('DefaultNodecolor')

              json = feature.getAttribute('JSON')

              physicsSolver = feature.getAttribute('PhysicsSolver')
              enablePhysics = feature.getAttribute('PhysicsEnabled')
              physicsMinVelocity = str(feature.getAttribute('PhysicsMinimumVelocity'))
              physicsAvoidOverlap = str(feature.getAttribute('PhysicsAvoidOverlap'))



              #Create new Network with 100% height and width
              net = Network(height='94%', width='100%', heading=heading)

              #load JSON into pandas dataframe
              df = pd.read_json(json, orient='records')
              print(df.head)

              #Create new networkx graph from pandas edgelist
              G = nx.from_pandas_edgelist(df, source="source", target="destination")

              #Create pyvis network from networkx graph
              net.from_nx(G)


              #Adjust Node Size & Color
              nodeSize = {}
              nodeColor = {}

              #Build size and Color Dicts
              for index, row in df.iterrows():
                  source = row['source']
                  destination = row['destination']
                  sourceColor = row['sourceColor']
                  destinationColor = row['destinationColor']


                  #Size Dict
                  if source not in nodeSize.keys():
                      nodeSize[source] = 10
                  else:
                      nodeSize[source] *= nodeSizeMultiplier
                  if destination not in nodeSize.keys():
                      nodeSize[destination] = 10
                  else:
                      nodeSize[destination] *= nodeSizeMultiplier

                  #Color Dict
                  if destination not in nodeColor.keys():
                      nodeColor[destination] = destinationColor
                  if source not in nodeColor.keys():
                      nodeColor[source] = sourceColor

              #Set node Size
              for n in net.nodes:
                  n['size'] = nodeSize[n['id']]

              #Set node Color
              for n in net.nodes:
                  if nodeColor[n['id']] != "" and nodeColor[n['id']] is not None:
                      n['color'] = nodeColor[n['id']]
                  else:
                      n['color'] = defaultNodeColor


              #Set node title
              neighbor_map = net.get_adj_list()

              for n in net.nodes:
                  n['title'] = ' Neighbors:' + '  |  '.join(neighbor_map[n['id']])

              #Set edge color
              for e in net.edges:
                  e['color'] = 'black'

              #Set pyvis network options
              net.set_options("""
                  const options = {
                    "nodes": {
                      "color": {
                        "highlight" : {
                          "border" : "rgba(129,11,233,1)"
                        }
                      },
                      "font": {
                        "size":""" + labelFontSize + """,
                        "face": "verdana",
                        "strokeWidth": 2
                      },
                      "shadow": {
                        "enabled": true,
                        "size": 9,
                        "x": 6,
                        "y": 7
                      },
                      "shapeProperties": {
                        "borderRadius": 3
                      },
                      "size": null
                    },
                    "physics": {
                      "enabled" :""" + enablePhysics + """,
                      """ + "\"" + physicsSolver + "\"" + """: {
                        "avoidOverlap": """ + physicsAvoidOverlap + """
                      },
                      "minVelocity": """ + physicsMinVelocity + """,
                      "solver": """ + "\"" + physicsSolver + "\"" + """
                    }
                  }
                  """)

              #Show network
              net.show(outputFile)

              outputFiles.append(outputFile)



          def close(self):
              """This method is called once all the FME Features have been processed
              from input().
              """
              print(outputFiles)
              for f in outputFiles:
                  newFeature = fmeobjects.FMEFeature()
                  newFeature.setAttribute('file_path', f)
                  self.pyoutput(newFeature)


          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> AttributeExposer
AttributeExposer
    ATTR_LIST = file_path
    -> AttributeKeeper
AttributeKeeper
    CREATE_BULK_MODE_FEATURES = NO
    KEEP_ATTRS = file_path
    -> HTMLFiles (output)
HTMLFiles (output)
BuildNetworkGraphs_2: PythonCaller [off]
    PYTHONSOURCE:
      import fme
      import fmeobjects
      import os
      import pandas as pd
      import networkx as nx
      import matplotlib
      matplotlib.use('agg')
      import matplotlib.pyplot as plt
      from pyvis.network import Network
      outputFiles = []




      class FeatureProcessor(object):
          """Template Class Interface:
          When using this class, make sure its name is set as the value of the 'Class
          to Process Features' transformer parameter.
          """



          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """

              heading = feature.getAttribute('Heading')
              outputPath = FME_MacroValues['FME_MF_DIR']
              outputFileName = f'{heading}.html'
              outputFile = os.path.join(outputPath, outputFileName)
              labelFontSize = str(feature.getAttribute('LabelFontSize'))
              nodeSizeMultiplier = float(feature.getAttribute('NodeSizeMultiplier'))
              defaultNodeColor = feature.getAttribute('DefaultNodecolor')

              json = feature.getAttribute('JSON')

              physicsSolver = feature.getAttribute('PhysicsSolver')
              enablePhysics = feature.getAttribute('PhysicsEnabled')
              physicsMinVelocity = str(feature.getAttribute('PhysicsMinimumVelocity'))
              physicsAvoidOverlap = str(feature.getAttribute('PhysicsAvoidOverlap'))



              #Create new Network with 100% height and width
              net = Network(height='94%', width='100%', heading=heading)

              #load JSON into pandas dataframe
              df = pd.read_json(json, orient='records')
              print(df.head)

              #Create new networkx graph from pandas edgelist
              G = nx.from_pandas_edgelist(df, source="source", target="destination")

              #Create pyvis network from networkx graph
              net.from_nx(G)


              #Adjust Node Size & Color
              nodeSize = {}
              nodeColor = {}

              #Build size and Color Dicts
              for index, row in df.iterrows():
                  source = row['source']
                  destination = row['destination']
                  sourceColor = row['sourceColor']
                  destinationColor = row['destinationColor']


                  #Size Dict
                  if source not in nodeSize.keys():
                      nodeSize[source] = 10
                  else:
                      nodeSize[source] *= nodeSizeMultiplier
                  if destination not in nodeSize.keys():
                      nodeSize[destination] = 10
                  else:
                      nodeSize[destination] *= nodeSizeMultiplier

                  #Color Dict
                  if destination not in nodeColor.keys():
                      nodeColor[destination] = destinationColor
                  if source not in nodeColor.keys():
                      nodeColor[source] = sourceColor

              #Set node Size
              for n in net.nodes:
                  n['size'] = nodeSize[n['id']]

              #Set node Color
              for n in net.nodes:
                  if nodeColor[n['id']] != "" and nodeColor[n['id']] is not None:
                      n['color'] = nodeColor[n['id']]
                  else:
                      n['color'] = defaultNodeColor


              #Set node title
              neighbor_map = net.get_adj_list()

              for n in net.nodes:
                  n['title'] = ' Neighbors:' + '  |  '.join(neighbor_map[n['id']])

              #Set edge color
              for e in net.edges:
                  e['color'] = 'black'

              #Set pyvis network options
              net.set_options("""
                  const options = {
                    "nodes": {
                      "color": {
                        "highlight" : {
                          "border" : "rgba(129,11,233,1)"
                        }
                      },
                      "font": {
                        "size":""" + labelFontSize + """,
                        "face": "verdana",
                        "strokeWidth": 2
                      },
                      "shadow": {
                        "enabled": true,
                        "size": 9,
                        "x": 6,
                        "y": 7
                      },
                      "shapeProperties": {
                        "borderRadius": 3
                      },
                      "size": null
                    },
                    "physics": {
                      "enabled" :""" + enablePhysics + """,
                      """ + "\"" + physicsSolver + "\"" + """: {
                        "avoidOverlap": """ + physicsAvoidOverlap + """
                      },
                      "minVelocity": """ + physicsMinVelocity + """,
                      "solver": "forceAtlas2Based"
                    }
                  }
                  """)

              #Show network
              net.show(outputFile)

              outputFiles.append(outputFile)



          def close(self):
              """This method is called once all the FME Features have been processed
              from input().
              """
              print(outputFiles)
              for f in outputFiles:
                  newFeature = fmeobjects.FMEFeature()
                  newFeature.setAttribute('file_path', f)
                  self.pyoutput(newFeature)


          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor

FME custom transformer Create_JSON_Stream

Parameters:
- pDestination =
- pDestinationColor =
- pHeading =
- pSource =
- pSourceColor =

Input (input)
    -> AttributeCreator
AttributeCreator
    ATTR_TABLE:
      SET_TO source = @Value($(pSource))
      SET_TO sourceColor = @Value($(pSourceColor))
      SET_TO destination = @Value($(pDestination))
      SET_TO destinationColor = @Value($(pDestinationColor))
    -> JSONTemplater_9 [ROOT]
JSONTemplater_9
    RESULT_ATTRIBUTE = _result
    ROOT_QUERY_EXPR:
      {
          "source": fme:get-attribute("source"),
          "sourceColor": fme:get-attribute("sourceColor"),
          "destination": fme:get-attribute("destination"),
          "destinationColor": fme:get-attribute("destinationColor")
      }
    VISIBLE_QUERY_VALIDATE = Yes
    -> JSONTemplater_8 [SUB]
Creator
    GEOMTYPE = Geometry Object
    NUM = 1
    CREATED -> JSONTemplater_8 [ROOT]
JSONTemplater_8
    RESULT_ATTRIBUTE = json
    ROOT_QUERY_EXPR:
      [
      fme:process-features("SUB")
      ]
    SUB_QUERY_EXPR = fme:get-json-attribute("_result")
    VISIBLE_QUERY_VALIDATE = Yes
    -> AttributeCreator_2
AttributeCreator_2
    ATTR_TABLE = SET_TO Heading = $(pHeading)
    -> Output (output)
Output (output)
